--
-- GEPON-OLT-VOICE-MIB.my
-- MIB generated by MG-SOFT Visual MIB Builder Version 5.0  Build 250
-- Tuesday, June 07, 2011 at 16:47:51
--

--  File Name : GEPON-OLT-VOICE-MIB.mib
-- Date      : Mon Jan 24 13:55:36 CST 2011
-- Author    : AdventNet Agent Toolkit C Edition - MibEditor 6

	GEPON-OLT-VOICE-MIB DEFINITIONS ::= BEGIN
 
		IMPORTS
			standard, slotIndex, onuIndex			
				FROM GEPON-OLT-COMMON-MIB			
			ifIndex			
				FROM IF-MIB			
			IpAddress, Integer32, OBJECT-TYPE			
				FROM SNMPv2-SMI			
			TruthValue, TEXTUAL-CONVENTION			
				FROM SNMPv2-TC;
	
	
--
-- Textual conventions
--
	
--  TEXTUAL-CONVENTIONS --
		MyTC ::= TEXTUAL-CONVENTION
			STATUS current
			DESCRIPTION 
				"TC Description"
			SYNTAX Integer32

	
--
-- Node definitions
--
	
		-- 1.3.6.1.4.1.5875.800.20
		oltVoice OBJECT IDENTIFIER ::= { standard 20 }

		
		-- 1.3.6.1.4.1.5875.800.20.1
		signalProfile OBJECT IDENTIFIER ::= { oltVoice 1 }

		
		-- 1.3.6.1.4.1.5875.800.20.1.1
		signalProfileTable OBJECT-TYPE
			SYNTAX SEQUENCE OF SignalProfileEntry
			MAX-ACCESS not-accessible
			STATUS current
			DESCRIPTION
				"Description"
			::= { signalProfile 1 }

		
		-- 1.3.6.1.4.1.5875.800.20.1.1.1
		signalProfileEntry OBJECT-TYPE
			SYNTAX SignalProfileEntry
			MAX-ACCESS not-accessible
			STATUS current
			DESCRIPTION
				"Row Description"
			INDEX { signalProfileId }
			::= { signalProfileTable 1 }

		
		SignalProfileEntry ::=
			SEQUENCE { 
				signalProfileId
					Integer32,
				signalName
					OCTET STRING,
				mgcProtocolType
					Integer32,
				mgc1Address
					OCTET STRING,
				mgc1Port
					Integer32,
				mgc2Address
					OCTET STRING,
				mgc2Port
					Integer32,
				mgc3Address
					OCTET STRING,
				mgc3Port
					Integer32,
				primaryDNS
					IpAddress,
				secondaryDNS
					IpAddress,
				sipRegistrationAddress
					OCTET STRING,
				sipRegistrationPort
					Integer32,
				sipServerAddress
					OCTET STRING,
				sipServerPort
					Integer32,
				sipTimeOut
					Integer32,
				keepAlive
					TruthValue,
				aliveInterval
					Integer32,
				aliveTime
					Integer32,
				signalProfileAction
					INTEGER
			 }

		-- 1.3.6.1.4.1.5875.800.20.1.1.1.1
		signalProfileId OBJECT-TYPE
			SYNTAX Integer32
			MAX-ACCESS read-only
			STATUS current
			DESCRIPTION
				"Column Description"
			::= { signalProfileEntry 1 }

		
		-- 1.3.6.1.4.1.5875.800.20.1.1.1.2
		signalName OBJECT-TYPE
			SYNTAX OCTET STRING
			MAX-ACCESS read-write
			STATUS current
			DESCRIPTION
				"Column Description"
			::= { signalProfileEntry 2 }

		
		-- 1.3.6.1.4.1.5875.800.20.1.1.1.3
		mgcProtocolType OBJECT-TYPE
			SYNTAX Integer32
			MAX-ACCESS read-write
			STATUS current
			DESCRIPTION
				"Column Description"
			::= { signalProfileEntry 3 }

		
		-- 1.3.6.1.4.1.5875.800.20.1.1.1.4
		mgc1Address OBJECT-TYPE
			SYNTAX OCTET STRING
			MAX-ACCESS read-write
			STATUS current
			DESCRIPTION
				"Column Description"
			::= { signalProfileEntry 4 }

		
		-- 1.3.6.1.4.1.5875.800.20.1.1.1.5
		mgc1Port OBJECT-TYPE
			SYNTAX Integer32
			MAX-ACCESS read-write
			STATUS current
			DESCRIPTION
				"Column Description"
			::= { signalProfileEntry 5 }

		
		-- 1.3.6.1.4.1.5875.800.20.1.1.1.6
		mgc2Address OBJECT-TYPE
			SYNTAX OCTET STRING
			MAX-ACCESS read-write
			STATUS current
			DESCRIPTION
				"Column Description"
			::= { signalProfileEntry 6 }

		
		-- 1.3.6.1.4.1.5875.800.20.1.1.1.7
		mgc2Port OBJECT-TYPE
			SYNTAX Integer32
			MAX-ACCESS read-write
			STATUS current
			DESCRIPTION
				"Column Description"
			::= { signalProfileEntry 7 }

		
		-- 1.3.6.1.4.1.5875.800.20.1.1.1.8
		mgc3Address OBJECT-TYPE
			SYNTAX OCTET STRING
			MAX-ACCESS read-write
			STATUS current
			DESCRIPTION
				"Column Description"
			::= { signalProfileEntry 8 }

		
		-- 1.3.6.1.4.1.5875.800.20.1.1.1.9
		mgc3Port OBJECT-TYPE
			SYNTAX Integer32
			MAX-ACCESS read-write
			STATUS current
			DESCRIPTION
				"Column Description"
			::= { signalProfileEntry 9 }

		
		-- 1.3.6.1.4.1.5875.800.20.1.1.1.10
		primaryDNS OBJECT-TYPE
			SYNTAX IpAddress
			MAX-ACCESS read-write
			STATUS current
			DESCRIPTION
				"Column Description"
			::= { signalProfileEntry 10 }

		
		-- 1.3.6.1.4.1.5875.800.20.1.1.1.11
		secondaryDNS OBJECT-TYPE
			SYNTAX IpAddress
			MAX-ACCESS read-write
			STATUS current
			DESCRIPTION
				"Column Description"
			::= { signalProfileEntry 11 }

		
		-- 1.3.6.1.4.1.5875.800.20.1.1.1.12
		sipRegistrationAddress OBJECT-TYPE
			SYNTAX OCTET STRING
			MAX-ACCESS read-write
			STATUS current
			DESCRIPTION
				"Column Description"
			::= { signalProfileEntry 12 }

		
		-- 1.3.6.1.4.1.5875.800.20.1.1.1.13
		sipRegistrationPort OBJECT-TYPE
			SYNTAX Integer32
			MAX-ACCESS read-write
			STATUS current
			DESCRIPTION
				"Column Description"
			::= { signalProfileEntry 13 }

		
		-- 1.3.6.1.4.1.5875.800.20.1.1.1.14
		sipServerAddress OBJECT-TYPE
			SYNTAX OCTET STRING
			MAX-ACCESS read-write
			STATUS current
			DESCRIPTION
				"Column Description"
			::= { signalProfileEntry 14 }

		
		-- 1.3.6.1.4.1.5875.800.20.1.1.1.15
		sipServerPort OBJECT-TYPE
			SYNTAX Integer32
			MAX-ACCESS read-write
			STATUS current
			DESCRIPTION
				"Column Description"
			::= { signalProfileEntry 15 }

		
		-- 1.3.6.1.4.1.5875.800.20.1.1.1.16
		sipTimeOut OBJECT-TYPE
			SYNTAX Integer32
			MAX-ACCESS read-write
			STATUS current
			DESCRIPTION
				"Column Description"
			::= { signalProfileEntry 16 }

		
		-- 1.3.6.1.4.1.5875.800.20.1.1.1.17
		keepAlive OBJECT-TYPE
			SYNTAX TruthValue
			MAX-ACCESS read-write
			STATUS current
			DESCRIPTION
				"Column Description"
			::= { signalProfileEntry 17 }

		
		-- 1.3.6.1.4.1.5875.800.20.1.1.1.18
		aliveInterval OBJECT-TYPE
			SYNTAX Integer32 (-2147483648..2147483647)
			MAX-ACCESS read-write
			STATUS current
			DESCRIPTION
				"Description"
			::= { signalProfileEntry 18 }

		
		-- 1.3.6.1.4.1.5875.800.20.1.1.1.19
		aliveTime OBJECT-TYPE
			SYNTAX Integer32 (-2147483648..2147483647)
			MAX-ACCESS read-write
			STATUS current
			DESCRIPTION
				"Description"
			::= { signalProfileEntry 19 }

		
		-- 1.3.6.1.4.1.5875.800.20.1.1.1.25
		signalProfileAction OBJECT-TYPE
			SYNTAX INTEGER
				{
				create(4),
				destory(6),
				modify(7)
				}
			MAX-ACCESS read-create
			STATUS current
			DESCRIPTION
				"Column Description"
			::= { signalProfileEntry 25 }

		
		-- 1.3.6.1.4.1.5875.800.20.1.2
		nextSignalProfileId OBJECT-TYPE
			SYNTAX Integer32
			MAX-ACCESS read-only
			STATUS current
			DESCRIPTION
				"Description"
			::= { signalProfile 2 }

		
		-- 1.3.6.1.4.1.5875.800.20.2
		potsUserCfg OBJECT IDENTIFIER ::= { oltVoice 2 }

		
		-- 1.3.6.1.4.1.5875.800.20.2.1
		potsUserCfgTable OBJECT-TYPE
			SYNTAX SEQUENCE OF PotsUserCfgEntry
			MAX-ACCESS not-accessible
			STATUS current
			DESCRIPTION
				"Description"
			::= { potsUserCfg 1 }

		
		-- 1.3.6.1.4.1.5875.800.20.2.1.1
		potsUserCfgEntry OBJECT-TYPE
			SYNTAX PotsUserCfgEntry
			MAX-ACCESS not-accessible
			STATUS current
			DESCRIPTION
				"Row Description"
			INDEX { ifIndex }
			::= { potsUserCfgTable 1 }

		
		PotsUserCfgEntry ::=
			SEQUENCE { 
				potsEnable
					TruthValue,
				telNum
					OCTET STRING,
				bindingSignalName
					OCTET STRING,
				signalVlan
					Integer32,
				svlanEnable
					TruthValue,
				svlanId
					Integer32,
				svlanCosFor5516
					Integer32,
				cvalnCosFor5516
					Integer32,
				voiceDomain
					OCTET STRING,
				protocolPort
					Integer32,
				userNameSipTelNum
					OCTET STRING,
				sipUserName
					OCTET STRING,
				sipPassword
					OCTET STRING,
				bindingPotsCfgProfileName
					OCTET STRING,
				potsUserCfgAction
					INTEGER
			 }

		-- 1.3.6.1.4.1.5875.800.20.2.1.1.2
		potsEnable OBJECT-TYPE
			SYNTAX TruthValue
			MAX-ACCESS read-write
			STATUS current
			DESCRIPTION
				"Column Description"
			::= { potsUserCfgEntry 2 }

		
		-- 1.3.6.1.4.1.5875.800.20.2.1.1.3
		telNum OBJECT-TYPE
			SYNTAX OCTET STRING
			MAX-ACCESS read-write
			STATUS current
			DESCRIPTION
				"Column Description"
			::= { potsUserCfgEntry 3 }

		
		-- 1.3.6.1.4.1.5875.800.20.2.1.1.4
		bindingSignalName OBJECT-TYPE
			SYNTAX OCTET STRING
			MAX-ACCESS read-write
			STATUS current
			DESCRIPTION
				"Column Description"
			::= { potsUserCfgEntry 4 }

		
		-- 1.3.6.1.4.1.5875.800.20.2.1.1.5
		signalVlan OBJECT-TYPE
			SYNTAX Integer32
			MAX-ACCESS read-write
			STATUS current
			DESCRIPTION
				"Column Description"
			::= { potsUserCfgEntry 5 }

		
		-- 1.3.6.1.4.1.5875.800.20.2.1.1.6
		svlanEnable OBJECT-TYPE
			SYNTAX TruthValue
			MAX-ACCESS read-write
			STATUS current
			DESCRIPTION
				"Column Description"
			::= { potsUserCfgEntry 6 }

		
		-- 1.3.6.1.4.1.5875.800.20.2.1.1.7
		svlanId OBJECT-TYPE
			SYNTAX Integer32
			MAX-ACCESS read-write
			STATUS current
			DESCRIPTION
				"Column Description"
			::= { potsUserCfgEntry 7 }

		
		-- 1.3.6.1.4.1.5875.800.20.2.1.1.8
		svlanCosFor5516 OBJECT-TYPE
			SYNTAX Integer32 (-2147483648..2147483647)
			MAX-ACCESS read-write
			STATUS current
			DESCRIPTION
				"only for 5516"
			::= { potsUserCfgEntry 8 }

		
		-- 1.3.6.1.4.1.5875.800.20.2.1.1.9
		cvalnCosFor5516 OBJECT-TYPE
			SYNTAX Integer32 (-2147483648..2147483647)
			MAX-ACCESS read-write
			STATUS current
			DESCRIPTION
				"only for 5516"
			::= { potsUserCfgEntry 9 }

		
		-- 1.3.6.1.4.1.5875.800.20.2.1.1.11
		voiceDomain OBJECT-TYPE
			SYNTAX OCTET STRING
			MAX-ACCESS read-write
			STATUS current
			DESCRIPTION
				"Column Description"
			::= { potsUserCfgEntry 11 }

		
		-- 1.3.6.1.4.1.5875.800.20.2.1.1.12
		protocolPort OBJECT-TYPE
			SYNTAX Integer32
			MAX-ACCESS read-write
			STATUS current
			DESCRIPTION
				"Column Description"
			::= { potsUserCfgEntry 12 }

		
		-- 1.3.6.1.4.1.5875.800.20.2.1.1.13
		userNameSipTelNum OBJECT-TYPE
			SYNTAX OCTET STRING
			MAX-ACCESS read-write
			STATUS current
			DESCRIPTION
				"Column Description"
			::= { potsUserCfgEntry 13 }

		
		-- 1.3.6.1.4.1.5875.800.20.2.1.1.14
		sipUserName OBJECT-TYPE
			SYNTAX OCTET STRING
			MAX-ACCESS read-write
			STATUS current
			DESCRIPTION
				"Column Description"
			::= { potsUserCfgEntry 14 }

		
		-- 1.3.6.1.4.1.5875.800.20.2.1.1.15
		sipPassword OBJECT-TYPE
			SYNTAX OCTET STRING
			MAX-ACCESS read-write
			STATUS current
			DESCRIPTION
				"Column Description"
			::= { potsUserCfgEntry 15 }

		
		-- 1.3.6.1.4.1.5875.800.20.2.1.1.16
		bindingPotsCfgProfileName OBJECT-TYPE
			SYNTAX OCTET STRING
			MAX-ACCESS read-write
			STATUS current
			DESCRIPTION
				"Description"
			::= { potsUserCfgEntry 16 }

		
		-- 1.3.6.1.4.1.5875.800.20.2.1.1.20
		potsUserCfgAction OBJECT-TYPE
			SYNTAX INTEGER { modify(7) }
			MAX-ACCESS read-write
			STATUS current
			DESCRIPTION
				"Column Description"
			::= { potsUserCfgEntry 20 }

		
		-- 1.3.6.1.4.1.5875.800.20.3
		onuVoiceCfg OBJECT IDENTIFIER ::= { oltVoice 3 }

		
		-- 1.3.6.1.4.1.5875.800.20.3.1
		onuVoiceCfgTable OBJECT-TYPE
			SYNTAX SEQUENCE OF OnuVoiceCfgEntry
			MAX-ACCESS not-accessible
			STATUS current
			DESCRIPTION
				"Description"
			::= { onuVoiceCfg 1 }

		
		-- 1.3.6.1.4.1.5875.800.20.3.1.1
		onuVoiceCfgEntry OBJECT-TYPE
			SYNTAX OnuVoiceCfgEntry
			MAX-ACCESS not-accessible
			STATUS current
			DESCRIPTION
				"Row Description"
			INDEX { onuIndex }
			::= { onuVoiceCfgTable 1 }

		
		OnuVoiceCfgEntry ::=
			SEQUENCE { 
				ipCfgType
					Integer32,
				staticIPAddress
					IpAddress,
				staticIPMask
					IpAddress,
				staticIPGateway
					IpAddress,
				pppoeUserName
					OCTET STRING,
				pppoePassword
					OCTET STRING,
				dhcpOption60Enable
					TruthValue,
				dhcpOption60Suffix
					OCTET STRING,
				bindingVoicePlatformProfileName
					OCTET STRING,
				voiceCfgAction
					INTEGER
			 }

		-- 1.3.6.1.4.1.5875.800.20.3.1.1.3
		ipCfgType OBJECT-TYPE
			SYNTAX Integer32 (-2147483648..2147483647)
			MAX-ACCESS read-write
			STATUS current
			DESCRIPTION
				"Column Description"
			::= { onuVoiceCfgEntry 3 }

		
		-- 1.3.6.1.4.1.5875.800.20.3.1.1.4
		staticIPAddress OBJECT-TYPE
			SYNTAX IpAddress
			MAX-ACCESS read-write
			STATUS current
			DESCRIPTION
				"Column Description"
			::= { onuVoiceCfgEntry 4 }

		
		-- 1.3.6.1.4.1.5875.800.20.3.1.1.5
		staticIPMask OBJECT-TYPE
			SYNTAX IpAddress
			MAX-ACCESS read-write
			STATUS current
			DESCRIPTION
				"Column Description"
			::= { onuVoiceCfgEntry 5 }

		
		-- 1.3.6.1.4.1.5875.800.20.3.1.1.6
		staticIPGateway OBJECT-TYPE
			SYNTAX IpAddress
			MAX-ACCESS read-write
			STATUS current
			DESCRIPTION
				"Column Description"
			::= { onuVoiceCfgEntry 6 }

		
		-- 1.3.6.1.4.1.5875.800.20.3.1.1.7
		pppoeUserName OBJECT-TYPE
			SYNTAX OCTET STRING
			MAX-ACCESS read-write
			STATUS current
			DESCRIPTION
				"Column Description"
			::= { onuVoiceCfgEntry 7 }

		
		-- 1.3.6.1.4.1.5875.800.20.3.1.1.8
		pppoePassword OBJECT-TYPE
			SYNTAX OCTET STRING
			MAX-ACCESS read-write
			STATUS current
			DESCRIPTION
				"Column Description"
			::= { onuVoiceCfgEntry 8 }

		
		-- 1.3.6.1.4.1.5875.800.20.3.1.1.9
		dhcpOption60Enable OBJECT-TYPE
			SYNTAX TruthValue
			MAX-ACCESS read-write
			STATUS current
			DESCRIPTION
				"Column Description"
			::= { onuVoiceCfgEntry 9 }

		
		-- 1.3.6.1.4.1.5875.800.20.3.1.1.10
		dhcpOption60Suffix OBJECT-TYPE
			SYNTAX OCTET STRING
			MAX-ACCESS read-write
			STATUS current
			DESCRIPTION
				"Column Description"
			::= { onuVoiceCfgEntry 10 }

		
		-- 1.3.6.1.4.1.5875.800.20.3.1.1.11
		bindingVoicePlatformProfileName OBJECT-TYPE
			SYNTAX OCTET STRING
			MAX-ACCESS read-write
			STATUS current
			DESCRIPTION
				"Description"
			::= { onuVoiceCfgEntry 11 }

		
		-- 1.3.6.1.4.1.5875.800.20.3.1.1.20
		voiceCfgAction OBJECT-TYPE
			SYNTAX INTEGER { modify(7) }
			MAX-ACCESS read-write
			STATUS current
			DESCRIPTION
				"Column Description"
			::= { onuVoiceCfgEntry 20 }

		
		-- 1.3.6.1.4.1.5875.800.20.6
		voicePlatformProfile OBJECT IDENTIFIER ::= { oltVoice 6 }

		
		-- 1.3.6.1.4.1.5875.800.20.6.1
		voicePlatformProfileTable OBJECT-TYPE
			SYNTAX SEQUENCE OF VoicePlatformProfileEntry
			MAX-ACCESS not-accessible
			STATUS current
			DESCRIPTION
				"Description"
			::= { voicePlatformProfile 1 }

		
		-- 1.3.6.1.4.1.5875.800.20.6.1.1
		voicePlatformProfileEntry OBJECT-TYPE
			SYNTAX VoicePlatformProfileEntry
			MAX-ACCESS not-accessible
			STATUS current
			DESCRIPTION
				"Row Description"
			INDEX { voicePlatformProfileId }
			::= { voicePlatformProfileTable 1 }

		
		VoicePlatformProfileEntry ::=
			SEQUENCE { 
				voicePlatformProfileId
					Integer32,
				voicePlatformProfileName
					OCTET STRING,
				rtpNameFiexedPart
					OCTET STRING,
				rtpBeginValue
					Integer32,
				rtpEndValue
					Integer32,
				rtpStepValue
					Integer32,
				rtpNameFill
					Integer32,
				digitmapStartTimer
					Integer32,
				digitmapShortTimer
					Integer32,
				digitmapLongTimer
					Integer32,
				dialMapNotifyImmediately
					Integer32,
				vbdEnable
					Integer32,
				packetIntervalOut
					Integer32,
				packetIntervalIn
					Integer32,
				codeType
					Integer32,
				platformProfileAction
					INTEGER
			 }

		-- 1.3.6.1.4.1.5875.800.20.6.1.1.1
		voicePlatformProfileId OBJECT-TYPE
			SYNTAX Integer32
			MAX-ACCESS read-only
			STATUS current
			DESCRIPTION
				"Column Description"
			::= { voicePlatformProfileEntry 1 }

		
		-- 1.3.6.1.4.1.5875.800.20.6.1.1.2
		voicePlatformProfileName OBJECT-TYPE
			SYNTAX OCTET STRING
			MAX-ACCESS read-write
			STATUS current
			DESCRIPTION
				"Column Description"
			::= { voicePlatformProfileEntry 2 }

		
		-- 1.3.6.1.4.1.5875.800.20.6.1.1.3
		rtpNameFiexedPart OBJECT-TYPE
			SYNTAX OCTET STRING
			MAX-ACCESS read-write
			STATUS current
			DESCRIPTION
				"Column Description"
			::= { voicePlatformProfileEntry 3 }

		
		-- 1.3.6.1.4.1.5875.800.20.6.1.1.4
		rtpBeginValue OBJECT-TYPE
			SYNTAX Integer32
			MAX-ACCESS read-write
			STATUS current
			DESCRIPTION
				"Column Description"
			::= { voicePlatformProfileEntry 4 }

		
		-- 1.3.6.1.4.1.5875.800.20.6.1.1.5
		rtpEndValue OBJECT-TYPE
			SYNTAX Integer32
			MAX-ACCESS read-write
			STATUS current
			DESCRIPTION
				"Column Description"
			::= { voicePlatformProfileEntry 5 }

		
		-- 1.3.6.1.4.1.5875.800.20.6.1.1.6
		rtpStepValue OBJECT-TYPE
			SYNTAX Integer32
			MAX-ACCESS read-write
			STATUS current
			DESCRIPTION
				"Column Description"
			::= { voicePlatformProfileEntry 6 }

		
		-- 1.3.6.1.4.1.5875.800.20.6.1.1.7
		rtpNameFill OBJECT-TYPE
			SYNTAX Integer32 (-2147483648..2147483647)
			MAX-ACCESS read-write
			STATUS current
			DESCRIPTION
				"Column Description"
			::= { voicePlatformProfileEntry 7 }

		
		-- 1.3.6.1.4.1.5875.800.20.6.1.1.8
		digitmapStartTimer OBJECT-TYPE
			SYNTAX Integer32
			MAX-ACCESS read-write
			STATUS current
			DESCRIPTION
				"Column Description"
			::= { voicePlatformProfileEntry 8 }

		
		-- 1.3.6.1.4.1.5875.800.20.6.1.1.9
		digitmapShortTimer OBJECT-TYPE
			SYNTAX Integer32
			MAX-ACCESS read-write
			STATUS current
			DESCRIPTION
				"Column Description"
			::= { voicePlatformProfileEntry 9 }

		
		-- 1.3.6.1.4.1.5875.800.20.6.1.1.10
		digitmapLongTimer OBJECT-TYPE
			SYNTAX Integer32
			MAX-ACCESS read-write
			STATUS current
			DESCRIPTION
				"Column Description"
			::= { voicePlatformProfileEntry 10 }

		
		-- 1.3.6.1.4.1.5875.800.20.6.1.1.11
		dialMapNotifyImmediately OBJECT-TYPE
			SYNTAX Integer32
			MAX-ACCESS read-write
			STATUS current
			DESCRIPTION
				"Column Description"
			::= { voicePlatformProfileEntry 11 }

		
		-- 1.3.6.1.4.1.5875.800.20.6.1.1.12
		vbdEnable OBJECT-TYPE
			SYNTAX Integer32
			MAX-ACCESS read-write
			STATUS current
			DESCRIPTION
				"Column Description"
			::= { voicePlatformProfileEntry 12 }

		
		-- 1.3.6.1.4.1.5875.800.20.6.1.1.13
		packetIntervalOut OBJECT-TYPE
			SYNTAX Integer32
			MAX-ACCESS read-write
			STATUS current
			DESCRIPTION
				"Column Description"
			::= { voicePlatformProfileEntry 13 }

		
		-- 1.3.6.1.4.1.5875.800.20.6.1.1.14
		packetIntervalIn OBJECT-TYPE
			SYNTAX Integer32
			MAX-ACCESS read-write
			STATUS current
			DESCRIPTION
				"Column Description"
			::= { voicePlatformProfileEntry 14 }

		
		-- 1.3.6.1.4.1.5875.800.20.6.1.1.15
		codeType OBJECT-TYPE
			SYNTAX Integer32
			MAX-ACCESS read-write
			STATUS current
			DESCRIPTION
				"Column Description"
			::= { voicePlatformProfileEntry 15 }

		
		-- 1.3.6.1.4.1.5875.800.20.6.1.1.16
		platformProfileAction OBJECT-TYPE
			SYNTAX INTEGER
				{
				create(4),
				destory(6),
				modify(7)
				}
			MAX-ACCESS read-create
			STATUS current
			DESCRIPTION
				"Column Description"
			::= { voicePlatformProfileEntry 16 }

		
		-- 1.3.6.1.4.1.5875.800.20.6.2
		nextVoicePlatformProfileId OBJECT-TYPE
			SYNTAX Integer32
			MAX-ACCESS read-only
			STATUS current
			DESCRIPTION
				"Description"
			::= { voicePlatformProfile 2 }

		
		-- 1.3.6.1.4.1.5875.800.20.7
		potsCfgProfile OBJECT IDENTIFIER ::= { oltVoice 7 }

		
		-- 1.3.6.1.4.1.5875.800.20.7.1
		potsCfgProfileTable OBJECT-TYPE
			SYNTAX SEQUENCE OF PotsCfgProfileEntry
			MAX-ACCESS not-accessible
			STATUS current
			DESCRIPTION
				"Description"
			::= { potsCfgProfile 1 }

		
		-- 1.3.6.1.4.1.5875.800.20.7.1.1
		potsCfgProfileEntry OBJECT-TYPE
			SYNTAX PotsCfgProfileEntry
			MAX-ACCESS not-accessible
			STATUS current
			DESCRIPTION
				"Row Description"
			INDEX { potsCfgProfileId }
			::= { potsCfgProfileTable 1 }

		
		PotsCfgProfileEntry ::=
			SEQUENCE { 
				potsCfgProfileId
					Integer32,
				potsCfgProfileName
					OCTET STRING,
				voiceCoder
					Integer32,
				faxMode
					Integer32,
				slienceSwitch
					TruthValue,
				echoCancel
					TruthValue,
				inputGain
					Integer32,
				outputGain
					Integer32,
				dtmfMode
					Integer32,
				faxCtrlMode
					Integer32,
				potsProfileAction
					INTEGER
			 }

		-- 1.3.6.1.4.1.5875.800.20.7.1.1.1
		potsCfgProfileId OBJECT-TYPE
			SYNTAX Integer32
			MAX-ACCESS read-only
			STATUS current
			DESCRIPTION
				"Column Description"
			::= { potsCfgProfileEntry 1 }

		
		-- 1.3.6.1.4.1.5875.800.20.7.1.1.2
		potsCfgProfileName OBJECT-TYPE
			SYNTAX OCTET STRING
			MAX-ACCESS read-write
			STATUS current
			DESCRIPTION
				"Column Description"
			::= { potsCfgProfileEntry 2 }

		
		-- 1.3.6.1.4.1.5875.800.20.7.1.1.3
		voiceCoder OBJECT-TYPE
			SYNTAX Integer32
			MAX-ACCESS read-write
			STATUS current
			DESCRIPTION
				"Column Description"
			::= { potsCfgProfileEntry 3 }

		
		-- 1.3.6.1.4.1.5875.800.20.7.1.1.4
		faxMode OBJECT-TYPE
			SYNTAX Integer32
			MAX-ACCESS read-write
			STATUS current
			DESCRIPTION
				"Column Description"
			::= { potsCfgProfileEntry 4 }

		
		-- 1.3.6.1.4.1.5875.800.20.7.1.1.5
		slienceSwitch OBJECT-TYPE
			SYNTAX TruthValue
			MAX-ACCESS read-write
			STATUS current
			DESCRIPTION
				"Column Description"
			::= { potsCfgProfileEntry 5 }

		
		-- 1.3.6.1.4.1.5875.800.20.7.1.1.6
		echoCancel OBJECT-TYPE
			SYNTAX TruthValue
			MAX-ACCESS read-write
			STATUS current
			DESCRIPTION
				"Column Description"
			::= { potsCfgProfileEntry 6 }

		
		-- 1.3.6.1.4.1.5875.800.20.7.1.1.7
		inputGain OBJECT-TYPE
			SYNTAX Integer32 (-2147483648..2147483647)
			MAX-ACCESS read-write
			STATUS current
			DESCRIPTION
				"Description"
			::= { potsCfgProfileEntry 7 }

		
		-- 1.3.6.1.4.1.5875.800.20.7.1.1.8
		outputGain OBJECT-TYPE
			SYNTAX Integer32 (-2147483648..2147483647)
			MAX-ACCESS read-write
			STATUS current
			DESCRIPTION
				"Description"
			::= { potsCfgProfileEntry 8 }

		
		-- 1.3.6.1.4.1.5875.800.20.7.1.1.9
		dtmfMode OBJECT-TYPE
			SYNTAX Integer32 (-2147483648..2147483647)
			MAX-ACCESS read-write
			STATUS current
			DESCRIPTION
				"Description"
			::= { potsCfgProfileEntry 9 }

		
		-- 1.3.6.1.4.1.5875.800.20.7.1.1.10
		faxCtrlMode OBJECT-TYPE
			SYNTAX Integer32
			MAX-ACCESS read-write
			STATUS current
			DESCRIPTION
				"Description"
			::= { potsCfgProfileEntry 10 }

		
		-- 1.3.6.1.4.1.5875.800.20.7.1.1.15
		potsProfileAction OBJECT-TYPE
			SYNTAX INTEGER
				{
				create(4),
				destory(6),
				modify(7)
				}
			MAX-ACCESS read-create
			STATUS current
			DESCRIPTION
				"Description"
			::= { potsCfgProfileEntry 15 }

		
		-- 1.3.6.1.4.1.5875.800.20.7.2
		nextPotsCfgProfileId OBJECT-TYPE
			SYNTAX Integer32
			MAX-ACCESS read-only
			STATUS current
			DESCRIPTION
				"Description"
			::= { potsCfgProfile 2 }

		
		-- 1.3.6.1.4.1.5875.800.20.8
		sipDigitmap OBJECT IDENTIFIER ::= { oltVoice 8 }

		
		-- 1.3.6.1.4.1.5875.800.20.8.1
		digitmap OBJECT-TYPE
			SYNTAX OCTET STRING
			MAX-ACCESS read-write
			STATUS current
			DESCRIPTION
				"Description"
			::= { sipDigitmap 1 }

		
	
	END

--
-- GEPON-OLT-VOICE-MIB.my
--
